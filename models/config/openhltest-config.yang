submodule openhltest-config {

    yang-version "1.1";
    belongs-to "openhltest" {
		prefix "oht";
	}

    include openhltest-port;
	include openhltest-device-groups;
	include openhltest-traffic-group;
	
    organization
      "OpenHlTest working group";
    contact
      "OpenHlTest working group";
    description
      "This sub-module aggregates all top level sub-modules that are configuration related.";

    revision 2017-11-02 {
        description
          "Initial revision.";
        reference
          "0.0.1";
    }

	grouping config-top {
		container config {
			description 
			"This container aggregates all other top level configuration submodules.";
			uses port-top;
			uses device-groups-top;
			uses traffic-group-top;

			action clear {
				description
				"Clear the current configuration";
			}
			action load {
				description
				"Load a vendor specific configuration";
				input {
					leaf vendor-config {
						description
						"Configuration data encoded as base64";
						type binary;
					}
				}
			}
		}
	}
}
