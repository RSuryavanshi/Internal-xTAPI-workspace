submodule openhltest-vlan {

    yang-version "1.1";
    belongs-to "openhltest" {
		prefix "oht";
	}

    import openhltest-types {
        prefix t;
    }
    
	organization
      "OpenHlTest working group";
    contact
      "OpenHlTest working group";
    description
      "This module describes a collection of emulated devices
	  and associated rpcs.";

    revision 2018-02-09 {
        description
          "Initial revision.";
        reference
          "0.0.1";
    }

    
    grouping vlan {
        description
        "A reuseable grouping of Vlan Interface";

		list vlan {
			key "name";
			description
			"A list of vlan interface group";
            
			leaf name {
				type string;
				description
				"The unique name of a vlan interface";
			}
			uses t:protocol-link-group;
			leaf vlan_id {
				type string;
				description
				"VLAN Identifier";
			}
			leaf priority {
				type string;
				description
				"VLAN Priority";
			}
			leaf tpid {
				type string;
				description
				"Tag Protocol Identifier";
			}
		}
	}    
}
