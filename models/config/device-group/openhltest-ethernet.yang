submodule openhltest-ethernet {

    yang-version "1.1";
    belongs-to "openhltest" {
		prefix "oht";
	}
    
    import openhltest-types {
        prefix t;
    }

	organization
      "OpenHlTest working group";
    contact
      "OpenHlTest working group";
    description
      "This module describes a collection of emulated devices
	  and associated rpcs.";

    revision 2018-02-09 {
        description
          "Initial revision.";
        reference
          "0.0.1";
    }

    grouping ethernet {
        description
        "A reuseable grouping of ethernet interface.";

		list ethernet {
			key "name";
			description
			"A list of ethernet interface groups";
            
			leaf name {
				type string;
				description
				"The unique name of an ethernet interface";
			}
			uses t:protocol-link-group;
            
			container mac_address {
            	description
				"MAC Address attribute";
                leaf value {
                    type string;
                    description
                    "Starting MAC Address value";
                }
                uses t:pattern;
			}
		}
	}    
}
