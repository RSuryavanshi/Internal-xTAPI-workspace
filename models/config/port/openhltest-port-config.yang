submodule openhltest-port-config {

    yang-version "1.1";
    belongs-to "openhltest" {
		prefix "oht";
	}

    organization
      "OpenHlTest working group";
    contact
      "OpenHlTest working group";
    description
      "This module describes a collection of abstract test ports
	  and associated rpcs. An abstract test port should be as 
	  minimal as possible.";

    revision 2017-11-02 {
        description
          "Initial revision.";
        reference
          "0.0.1";
    }

    grouping port-config-top {
        description
          "A grouping of abstract test ports";

        container config-ports {
            list port-map {
                key "port_name";
                leaf port_name {
                    description "The name of an abstract test port";
                    type string;
                }
                leaf speed {
                    type string;
                    description 
                        "Maximum transfer Unit";
                }
                leaf media {
                    type string;
                    description
                        "Physical media";
                }
            }

            list aggregate-port {
                key 'port_group_name';
                leaf port_group_name {
                    type string;
                    description 
                        "Aggregate port name";
                }
                leaf-list member-port-names {
                    type string;
                    description
                        "Physical media";
                }
                leaf transmit-algorithm {
                     type string;
                     description
                        "Physical media";
                }
            }
        }
	}
}
