submodule openhltest-traffic-ethernet-group {

    yang-version "1.1";
    belongs-to "openhltest" {
		prefix "oht";
	}

    import openhltest-types {
        prefix t;
    }
	
    organization
      "OpenHlTest working group";
    contact
      "OpenHlTest working group";
    description
      "This module describes a collection of traffic groups
	  and associated rpcs.";

    revision 2018-02-09 {
        description
          "Initial revision.";
        reference
          "0.0.1";
    }

    grouping traffic-ethernet-group-top {
        description
        "A grouping of traffic groups.
		 A traffic group is a collection of traffic streams and flows.";
		
        list ethernet-header {
            key "name";
            description
            "A list frames";
            
            leaf name {
                type string;
                description
                "The unique name";
            }
            leaf header-link {
                type string;
                description
                "The unique name";
            }
            container src_mac {
                description
                "MAC Address attribute";
                leaf value {
                    type string;
                    description
                    "Starting MAC Address value";
                }
                uses t:pattern;
            }
            container dest_mac {
                description
                "MAC Address attribute";
                leaf value {
                    type string;
                    description
                    "Starting MAC Address value";
                }
                uses t:pattern;
            }
        }
        /*list ipv4-header {
            key "name";
            description
            "A list frames";
            
            leaf name {
                type string;
                description
                "The unique name";
            }
            leaf header-link {
                type string;
                description
                "The unique name";
            }
            container src_address {
                description
                "MAC Address attribute";
                leaf value {
                    type string;
                    description
                    "Starting MAC Address value";
                }
                uses t:pattern;
            }
            container dest_address {
                description
                "MAC Address attribute";
                leaf value {
                    type string;
                    description
                    "Starting MAC Address value";
                }
                uses t:pattern;
            }
            container ttl {
                description
                "MAC Address attribute";
                leaf value {
                    type string;
                    description
                    "Starting MAC Address value";
                }
                uses t:pattern;
            }
        }*/
    }

}
