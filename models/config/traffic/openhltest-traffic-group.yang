submodule openhltest-traffic-group {

    yang-version "1.1";
    belongs-to "openhltest" {
		prefix "oht";
	}

    import openhltest-types {
        prefix t;
    }
	

    include openhltest-traffic-ethernet-group;
    include openhltest-traffic-vlan-group;
    include openhltest-traffic-ipv4-group;
    include openhltest-traffic-ipv6-group;

    organization
      "OpenHlTest working group";
    contact
      "OpenHlTest working group";
    description
      "This module describes a collection of traffic groups
	  and associated rpcs.";

    revision 2018-02-09 {
        description
          "Initial revision.";
        reference
          "0.0.1";
    }

    grouping traffic-group-top {
        description
        "A grouping of traffic groups.
		 A traffic group is a collection of traffic streams and flows.";
		
		list traffic-groups {
			key "name";
			description
			"A list of traffic groups";

			leaf name {
				type t:config-list-key;
				description
				"The unique name of a traffic group";
			}
            leaf endpoint-mapping {
                type enumeration {
                    enum ONE_TO_ONE;
                    enum FULL_MESHED;
                }
                description
                  "The endpoint mapping";
            }
			leaf-list source-endpoints {
				type string;
				description
				"Source endpoints, devices name";
			}
			leaf-list destination-endpoints {
				type string;
				description
				"Destination endpoints, devices name";
			}
            leaf encapsulation {
                type enumeration {
                    enum ETHERNET;
                    enum VLAN;
                    enum IPV4;
                    enum IPV6;
                }
                description
                  "The type of encapsulation that will determine the type of generated frames 
                  and associated learned info";
            }
            
			container frame-length {
                container fixed-mode {
                    leaf frame-size {
                        type int32;
                        description
                        "Fixed value for frame length";
                    }
                }
			}
            
            container frame-load {
                leaf value {
                    type int32;
                    description
                    "Load value set on the streamblock/traffic-item. Load has different 
                    meanings, based on load unit.";
                }
                leaf unit {
                    description
                    "Load unit applied to the stream block.";
                    type enumeration {
                        enum bps;
                        enum kbps;
                        enum mbps;
                        enum fps;
                    }
                }
            }

            leaf bidirectional {
                type boolean;
                description
                "Direction of traffic flow between two end points";
            }
            
            container frame {
                description
                "A list frames";
                uses traffic-ethernet-group-top;
                uses traffic-vlan-group-top;
                uses traffic-ipv4-group-top;
                uses traffic-ipv6-group-top;
            }
            
		}

		action start-traffic {
			description
			"Start one or more traffic groups.
			An empty list signifies that all traffic groups will be started.";

			input {
				leaf-list traffic-group-names {
					description "A list of traffic group names";
					type string;
				}
			}
			output {
				uses t:errata-group {
					description "A list of traffic group resources that failed to start.
					An empty list signifies that all traffic groups successfully started.";
				}
			}
		}
		action stop-traffic {
			description
			"Stop one or more traffic groups. 
			An empty list signifies that all traffic groups will be stopped.";

			input {
				leaf-list traffic-group-names {
					description "A list of traffic group names";
					type string;
				}
			}
			output {
				uses t:errata-group {
					description "A list of traffic group resources that failed to start.
					An empty list signifies that all traffic groups successfully stopped.";
				}
			}
		}
    }
}
