submodule openhltest-statistics {

    yang-version "1.1";
    belongs-to "openhltest" {
		prefix "oht";
	}

	import ietf-yang-types {
		prefix yang;
	}
	include openhltest-port-statistics;
    include openhltest-bgp-statistics;

    organization
      "OpenHlTest working group";
    contact
      "OpenHlTest working group";
    description
      "This module describes a collection of all statistics that are available.
	  It offers two methods of statistic retrieval.
	  The pull method is described under the statistics container.
	  The push method is described under the statistic-events container.";

    revision 2017-11-02 {
        description
          "Initial revision.";
        reference
          "0.0.1";
    }

	grouping statistics-top {

        /*leaf result-type {
            type enumeration {
                enum PORT;
                enum BGP4;
            }
            default "PORT";
        }*/
        
        leaf-list port-name {
            type string;
            description
            "The list of port-names";
        }

		leaf first-activity-timestamp {
			config false;
			description "Timestamp of the first request to this session.";
			type yang:date-and-time;
		}
		leaf last-activity-timestamp {
			config false;
			description "Timestamp of the last request to this session";
			type yang:date-and-time;
		}		
		
		uses port-statistics-top;
        uses bgp4-statistics;
        uses bgp6-statistics;
	}
}
