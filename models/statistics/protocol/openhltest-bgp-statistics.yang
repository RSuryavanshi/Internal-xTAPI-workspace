submodule openhltest-bgp-statistics {

    yang-version "1.1";
    belongs-to "openhltest" {
		prefix "oht";
	}

    organization
      "OpenHlTest working group";
    contact
      "OpenHlTest working group";
    description
      "This module describes a YANG model for 
       abstract test port statistics.";

    revision 2017-11-02 {
        description
          "Initial revision.";
        reference
          "0.0.1";
    }

    grouping bgp-statistics {
        description
          "A grouping of port statistics";
          
        list bgp-statistics {

			key "device_group_name";
			leaf port_name {
				description "An abstract test port name";
				type string;
			}
			leaf device_group_name {
				description "An abstract test port name";
				type string;
			}
			config false;
            
            leaf router-state {
                config false;
                type enumeration {
                    enum IDLE;
                    enum CONNECTING;
                    enum ESTABLISHED;
                }
                description
                  "The state of the connection to the physical hardware 
                   test port or virtual machine test port";
            }
            leaf tx-advertise-route-count {
                config false;
                type string;
                description
                  "The total number of frames transmitted on the port.
                  Empty if the abstract port is not connected to a test port.";
            }
            leaf rx-advertise-route-count {
                config false;
                type string;
                description
                  "The total number of frames received on the the port.
                  Empty if the abstract port is not connected to a test port.";
            }
            leaf tx-withdraw-route-count {
                config false;
                type string;
                description
                  "The total number of frames transmitted on the port.
                  Empty if the abstract port is not connected to a test port.";
            }
            leaf rx-withdraw-route-count {
                config false;
                type string;
                description
                  "The total number of frames received on the the port.
                  Empty if the abstract port is not connected to a test port.";
            }
        }
    }
}
