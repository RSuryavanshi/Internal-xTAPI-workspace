module openhltest {

	yang-version "1.1";
	namespace "http://openhltest.org/yang/oht";
	prefix "oht";

	include openhltest-sessions;
	include openhltest-config;
	include openhltest-port;
	include openhltest-device-groups;
    
	include openhltest-ethernet;
	include openhltest-vlan;
	include openhltest-ipv4;
    include openhltest-ipv6;
    
    include openhltest-bgp-common;
	include openhltest-bgp4;
	include openhltest-bgp6;
	
    include openhltest-traffic-group;
    include openhltest-traffic-ethernet-group;
    include openhltest-traffic-vlan-group;
    include openhltest-traffic-ipv4-group;
    include openhltest-traffic-ipv6-group;
	
    include openhltest-statistics;
	include openhltest-port-statistics;
    include openhltest-bgp-statistics;
	
    include openhltest-ipv4-route-range;
    include openhltest-ipv6-route-range;
	include openhltest-bgp4-route-range;
    include openhltest-bgp6-route-range;

	organization
	"OpenHlTest working group";
	contact
	"OpenHlTest working group";
	description
	"This module is the top level of the test hierarchy.";

	revision 2018-01-01 {
		description
		"Initial revision.";
		reference
		"0.0.1";
	}

	uses session-top;
}
